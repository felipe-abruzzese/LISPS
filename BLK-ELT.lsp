;; LISP COM COMANDOS DE ELÉTRICA ESCRITÓRIO NBR GROUP
;; AUTOR: FELIPE ABRUZZESE
;; VERSÃO: 1.2



(VMON) 

;; ----------------------------------------------- TAG -----------------------------------------------------------

(DEFUN C:111 () (COMMAND "-LINETYPE" "S" "BYLAYER" "" "" "-COLOR" "YELLOW" "-LAYER" "S" "_NBR-PT-ELE-COM" "" "-COLOR" "YELLOW" "-INSERT" "E-CKT-25" "S" "1")) ;; 		TAG 1/25 | COMUM
(DEFUN C:112 () (COMMAND "-LINETYPE" "S" "BYLAYER" "" "" "-COLOR" "YELLOW" "-LAYER" "S" "_NBR-PT-ELE-EST" "" "-COLOR" "YELLOW" "-INSERT" "E-CKT-25" "S" "1")) ;; 		TAG 1/25 | ESTABILIZADO

(DEFUN C:121 () (COMMAND "-LINETYPE" "S" "BYLAYER" "" "" "-COLOR" "YELLOW" "-LAYER" "S" "_NBR-PT-ELE-COM" "" "-COLOR" "YELLOW" "-INSERT" "E-CKT-50" "S" "1")) ;; 		TAG 1/50 | COMUM
(DEFUN C:122 () (COMMAND "-LINETYPE" "S" "BYLAYER" "" "" "-COLOR" "YELLOW" "-LAYER" "S" "_NBR-PT-ELE-EST" "" "-COLOR" "YELLOW" "-INSERT" "E-CKT-50" "S" "1")) ;; 		TAG 1/50 | ESTABILIZADO

(DEFUN C:131 () (COMMAND "-LINETYPE" "S" "BYLAYER" "" "" "-COLOR" "YELLOW" "-LAYER" "S" "_NBR-PT-ELE-COM" "" "-COLOR" "YELLOW" "-INSERT" "E-CKT-75" "S" "1")) ;; 		TAG 1/75 | COMUM
(DEFUN C:132 () (COMMAND "-LINETYPE" "S" "BYLAYER" "" "" "-COLOR" "YELLOW" "-LAYER" "S" "_NBR-PT-ELE-EST" "" "-COLOR" "YELLOW" "-INSERT" "E-CKT-75" "S" "1")) ;; 		TAG 1/75 | ESTABILIZADO

(DEFUN C:141 () (COMMAND "-LINETYPE" "S" "BYLAYER" "" "" "-COLOR" "YELLOW" "-LAYER" "S" "_NBR-PT-ELE-COM" "" "-COLOR" "YELLOW" "-INSERT" "E-CKT-100" "S" "1")) ;; 		TAG 1/100 | COMUM
(DEFUN C:142 () (COMMAND "-LINETYPE" "S" "BYLAYER" "" "" "-COLOR" "YELLOW" "-LAYER" "S" "_NBR-PT-ELE-EST" "" "-COLOR" "YELLOW" "-INSERT" "E-CKT-100" "S" "1")) ;; 		TAG 1/100 | ESTABILIZADO

;; ----------------------------------------------- ACESSÓRIOS DE INSTALAÇÃO -----------------------------------------------------------

(DEFUN C:211 () (COMMAND "-LINETYPE" "S" "BYLAYER" "" "" "-COLOR" "BYLAYER" ""  "-LAYER" "S" "_NBR-ELE-COM-CALHA" "" "-INSERT" "E-ELT" "S" "1")) ;; 	DESCIDA / SUBIDA DE ELETRODUTO | COMUM
(DEFUN C:212 () (COMMAND "-LINETYPE" "S" "BYLAYER" "" "" "-COLOR" "BYLAYER" ""  "-LAYER" "S" "_NBR-ELE-EST-CALHA" "" "-INSERT" "E-ELT" "S" "1")) ;; 	DESCIDA / SUBIDA DE ELETRODUTO | ESTABILIZADO
(DEFUN C:213 () (COMMAND "-LINETYPE" "S" "BYLAYER" "" "" "-COLOR" "BYLAYER" ""  "-LAYER" "S" "_NBR-CAB-CALHA" "" "-INSERT" "E-ELT" "S" "1")) ;; 		DESCIDA / SUBIDA DE ELETRODUTO | CABEAMENTO
(DEFUN C:214 () (COMMAND "-LINETYPE" "S" "BYLAYER" "" "" "-COLOR" "BYLAYER" ""  "-LAYER" "S" "_NBR-MULT-CALHA" "" "-INSERT" "E-ELT" "S" "1")) ;; 	DESCIDA / SUBIDA DE ELETRODUTO | MULTIMÍDIA
(DEFUN C:215 () (COMMAND "-LINETYPE" "S" "BYLAYER" "" "" "-COLOR" "BYLAYER" ""  "-LAYER" "S" "_NBR-CFTV-CALHA" "" "-INSERT" "E-ELT" "S" "1")) ;; 	DESCIDA / SUBIDA DE ELETRODUTO | CFTV
(DEFUN C:216 () (COMMAND "-LINETYPE" "S" "BYLAYER" "" "" "-COLOR" "BYLAYER" ""  "-LAYER" "S" "_NBR-BACKBONE-CALHA" "" "-INSERT" "E-ELT" "S" "1")) ;; 	DESCIDA / SUBIDA DE ELETRODUTO | BACKBONE
(DEFUN C:2112 () (COMMAND "-LINETYPE" "S" "BYLAYER" "" "" "-COLOR" "BYLAYER" ""  "-LAYER" "S" "_NBR-ELE-ILUEM" "" "-INSERT" "E-ELT" "S" "1")) ;; 	DESCIDA / SUBIDA DE ELETRODUTO | ILUEM

(DEFUN C:221 () (COMMAND "-LINETYPE" "S" "BYLAYER" "" "" "-COLOR" "BYLAYER" ""  "-LAYER" "S" "_NBR-ELE-COM-CALHA" "" "-INSERT" "E-CONDULETE" "S" "1")) ;; 		CONDULETE | COMUM
(DEFUN C:222 () (COMMAND "-LINETYPE" "S" "BYLAYER" "" "" "-COLOR" "BYLAYER" ""  "-LAYER" "S" "_NBR-ELE-EST-CALHA" "" "-INSERT" "E-CONDULETE" "S" "1")) ;; 		CONDULETE | ESTABILIZADO
(DEFUN C:223 () (COMMAND "-LINETYPE" "S" "BYLAYER" "" "" "-COLOR" "BYLAYER" ""  "-LAYER" "S" "_NBR-CAB-CALHA" "" "-INSERT" "E-CONDULETE" "S" "1")) ;; 			CONDULETE | CABEAMENTO
(DEFUN C:224 () (COMMAND "-LINETYPE" "S" "BYLAYER" "" "" "-COLOR" "BYLAYER" ""  "-LAYER" "S" "_NBR-MULT-CALHA" "" "-INSERT" "E-CONDULETE" "S" "1")) ;; 	CONDULETE | MULTIMÍDIA
(DEFUN C:225 () (COMMAND "-LINETYPE" "S" "BYLAYER" "" "" "-COLOR" "BYLAYER" ""  "-LAYER" "S" "_NBR-CFTV-CALHA" "" "-INSERT" "E-CONDULETE" "S" "1")) ;; 	CONDULETE | CFTV
(DEFUN C:226 () (COMMAND "-LINETYPE" "S" "BYLAYER" "" "" "-COLOR" "BYLAYER" ""  "-LAYER" "S" "_NBR-BACKBONE-CALHA" "" "-INSERT" "E-CONDULETE" "S" "1")) ;; 	CONDULETE | BACKBONE
(DEFUN C:2212 () (COMMAND "-LINETYPE" "S" "BYLAYER" "" "" "-COLOR" "BYLAYER" ""  "-LAYER" "S" "_NBR-ELE-ILUEM" "" "-INSERT" "E-CONDULETE" "S" "1")) ;; 	CONDULETE | ILUEM


(DEFUN C:231 () (COMMAND "-LINETYPE" "S" "BYLAYER" "" "" "-COLOR" "BYLAYER" ""  "-LAYER" "S" "_NBR-ELE-COM-CALHA" "" "-INSERT" "E-CX PASS" "S" "1")) ;; 	CAIXA | COMUM
(DEFUN C:232 () (COMMAND "-LINETYPE" "S" "BYLAYER" "" "" "-COLOR" "BYLAYER" ""  "-LAYER" "S" "_NBR-ELE-EST-CALHA" "" "-INSERT" "E-CX PASS" "S" "1")) ;; 	CAIXA | ESTABILIZADO
(DEFUN C:233 () (COMMAND "-LINETYPE" "S" "BYLAYER" "" "" "-COLOR" "BYLAYER" ""  "-LAYER" "S" "_NBR-CAB-CALHA" "" "-INSERT" "E-CX PASS" "S" "1")) ;; 		CAIXA | CABEAMENTO
(DEFUN C:234 () (COMMAND "-LINETYPE" "S" "BYLAYER" "" "" "-COLOR" "BYLAYER" ""  "-LAYER" "S" "_NBR-MULT-CALHA" "" "-INSERT" "E-CX PASS" "S" "1")) ;; 	CAIXA | MULTIMÍDIA
(DEFUN C:235 () (COMMAND "-LINETYPE" "S" "BYLAYER" "" "" "-COLOR" "BYLAYER" ""  "-LAYER" "S" "_NBR-CFTV-CALHA" "" "-INSERT" "E-CX PASS" "S" "1")) ;; 	CAIXA | CFTV
(DEFUN C:236 () (COMMAND "-LINETYPE" "S" "BYLAYER" "" "" "-COLOR" "BYLAYER" ""  "-LAYER" "S" "_NBR-BACKBONE-CALHA" "" "-INSERT" "E-CX PASS" "S" "1")) ;; 	CAIXA | BACKBONE
(DEFUN C:2312 () (COMMAND "-LINETYPE" "S" "BYLAYER" "" "" "-COLOR" "BYLAYER" ""  "-LAYER" "S" "_NBR-ELE-ILUEM" "" "-INSERT" "E-CX PASS" "S" "1")) ;; 	CAIXA | ILUEM


(DEFUN C:241 () (COMMAND "-LINETYPE" "S" "BYLAYER" "" "" "-COLOR" "BYLAYER" ""  "-LAYER" "S" "_NBR-ELE-COM-CALHA" "" "-INSERT" "E-SOBE DESCE CALHA" "S" "1")) ;; 		SUBIDA / DESCIDA ELETROCALHA | COMUM
(DEFUN C:242 () (COMMAND "-LINETYPE" "S" "BYLAYER" "" "" "-COLOR" "BYLAYER" ""  "-LAYER" "S" "_NBR-ELE-EST-CALHA" "" "-INSERT" "E-SOBE DESCE CALHA" "S" "1")) ;; 		SUBIDA / DESCIDA ELETROCALHA | ESTABILIZADO
(DEFUN C:243 () (COMMAND "-LINETYPE" "S" "BYLAYER" "" "" "-COLOR" "BYLAYER" ""  "-LAYER" "S" "_NBR-CAB-CALHA" "" "-INSERT" "E-SOBE DESCE CALHA" "S" "1")) ;; 			SUBIDA / DESCIDA ELETROCALHA | CABEAMENTO
(DEFUN C:244 () (COMMAND "-LINETYPE" "S" "BYLAYER" "" "" "-COLOR" "BYLAYER" ""  "-LAYER" "S" "_NBR-MULT-CALHA" "" "-INSERT" "E-SOBE DESCE CALHA" "S" "1")) ;; 		SUBIDA / DESCIDA ELETROCALHA | MULTIMÍDIA
(DEFUN C:245 () (COMMAND "-LINETYPE" "S" "BYLAYER" "" "" "-COLOR" "BYLAYER" ""  "-LAYER" "S" "_NBR-CFTV-CALHA" "" "-INSERT" "E-SOBE DESCE CALHA" "S" "1")) ;; 		SUBIDA / DESCIDA ELETROCALHA | CFTV
(DEFUN C:246 () (COMMAND "-LINETYPE" "S" "BYLAYER" "" "" "-COLOR" "BYLAYER" ""  "-LAYER" "S" "_NBR-BACKBONE-CALHA" "" "-INSERT" "E-SOBE DESCE CALHA" "S" "1")) ;; 		SUBIDA / DESCIDA ELETROCALHA | BACKBONE
(DEFUN C:2412 () (COMMAND "-LINETYPE" "S" "BYLAYER" "" "" "-COLOR" "BYLAYER" ""  "-LAYER" "S" "_NBR-ELE-ILUEM" "" "-INSERT" "E-SOBE DESCE CALHA" "S" "1")) ;; 		SUBIDA / DESCIDA ELETROCALHA | ILUEM


;; -------------------------------------------------- EQUIPAMENTOS ------------------------------------------------------- 

(DEFUN C:311 () (COMMAND "-LINETYPE" "S" "BYLAYER" "" "" "-COLOR" "BYLAYER" ""  "-LAYER" "S" "_NBR-QD-NOVO" "" "-INSERT" "E-QUADRO" "S" "1")) ;; 	QUADRO
(DEFUN C:312 () (COMMAND "-LINETYPE" "S" "BYLAYER" "" "" "-COLOR" "BYLAYER" ""  "-LAYER" "S" "_NBR-ELE-COM-CALHA" "" "-INSERT" "E-CX SPERONE" "S" "1")) ;; 	CAIXA SPERONE 
(DEFUN C:313 () (COMMAND "-LINETYPE" "S" "BYLAYER" "" "" "-COLOR" "BYLAYER" ""  "-LAYER" "S" "_NBR-ELE-COM-CALHA" "" "-INSERT" "E-PF-MONO" "S" "1")) ;; 	PONTO DE FORÇA MONOFÁSICO
(DEFUN C:314 () (COMMAND "-LINETYPE" "S" "BYLAYER" "" "" "-COLOR" "BYLAYER" ""  "-LAYER" "S" "_NBR-ELE-COM-CALHA" "" "-INSERT" "E-PF-TRI" "S" "1")) ;; 	PONTO DE FORÇA TRIFÁSICO
(DEFUN C:315 () (COMMAND "-LINETYPE" "S" "BYLAYER" "" "" "-COLOR" "BYLAYER" ""  "-LAYER" "S" "_NBR-CAB-CALHA" "" "-INSERT" "E-PT WIFI" "S" "1")) ;; 	PONTO DE WIFI
(DEFUN C:315 () (COMMAND "-LINETYPE" "S" "BYLAYER" "" "" "-COLOR" "BYLAYER" ""  "-LAYER" "S" "_NBR-CAB-CALHA" "" "-INSERT" "E-CAMERA" "S" "1")) ;; 	PONTO DE WIFI



;; -------------------------------------------------- CALHAS E PERFILADO------------------------------------------------------- 

(DEFUN C:411 () (COMMAND "-LINETYPE" "S" "BYLAYER" "" "" "-COLOR" "BYLAYER" ""  "-LAYER" "S" "_NBR-ELE-COM-CALHA" "" "-INSERT" "E-CON-CALHA" "S" "1")) ;; 		CONEXÕES ELETROCALHA | COMUM
(DEFUN C:412 () (COMMAND "-LINETYPE" "S" "BYLAYER" "" "" "-COLOR" "BYLAYER" ""  "-LAYER" "S" "_NBR-ELE-EST-CALHA" "" "-INSERT" "E-CON-CALHA" "S" "1")) ;; 		CONEXÕES ELETROCALHA | ESTABILIZADO
(DEFUN C:413 () (COMMAND "-LINETYPE" "S" "BYLAYER" "" "" "-COLOR" "BYLAYER" ""  "-LAYER" "S" "_NBR-CAB-CALHA" "" "-INSERT" "E-CON-CALHA" "S" "1")) ;; 			CONEXÕES ELETROCALHA | CABEAMENTO
(DEFUN C:414 () (COMMAND "-LINETYPE" "S" "BYLAYER" "" "" "-COLOR" "BYLAYER" ""  "-LAYER" "S" "_NBR-MULT-CALHA" "" "-INSERT" "E-CON-CALHA" "S" "1")) ;;		CONEXÕES ELETROCALHA | MULTIMÍDIA
(DEFUN C:415 () (COMMAND "-LINETYPE" "S" "BYLAYER" "" "" "-COLOR" "BYLAYER" ""  "-LAYER" "S" "_NBR-CFTV-CALHA" "" "-INSERT" "E-CON-CALHA" "S" "1")) ;; 		CONEXÕES ELETROCALHA | CFTV
(DEFUN C:416 () (COMMAND "-LINETYPE" "S" "BYLAYER" "" "" "-COLOR" "BYLAYER" ""  "-LAYER" "S" "_NBR-BACKBONE-CALHA" "" "-INSERT" "E-CON-CALHA" "S" "1")) ;; 		CONEXÕES ELETROCALHA | BACKBONE

(DEFUN C:421 () (COMMAND "-LINETYPE" "S" "BYLAYER" "" "" "-COLOR" "BYLAYER" ""  "-LAYER" "S" "_NBR-ELE-COM-CALHA" "" "-INSERT" "E-CALHA ELE COM" "S" "1")) ;; 		ELETROCALHA | COMUM
(DEFUN C:422 () (COMMAND "-LINETYPE" "S" "BYLAYER" "" "" "-COLOR" "BYLAYER" ""  "-LAYER" "S" "_NBR-ELE-EST-CALHA" "" "-INSERT" "E-CALHA ELE EST" "S" "1")) ;; 		ELETROCALHA | ESTABILIZADO
(DEFUN C:423 () (COMMAND "-LINETYPE" "S" "BYLAYER" "" "" "-COLOR" "BYLAYER" ""  "-LAYER" "S" "_NBR-CAB-CALHA" "" "-INSERT" "E-CALHA DADOS" "S" "1")) ;; 			ELETROCALHA | CABEAMENTO
(DEFUN C:424 () (COMMAND "-LINETYPE" "S" "BYLAYER" "" "" "-COLOR" "BYLAYER" ""  "-LAYER" "S" "_NBR-MULT-CALHA" "" "-INSERT" "E-CALHA MULTIMIDIA" "S" "1")) ;; ELETROCALHA | MULTIMÍDIA
(DEFUN C:425 () (COMMAND "-LINETYPE" "S" "BYLAYER" "" "" "-COLOR" "BYLAYER" ""  "-LAYER" "S" "_NBR-CFTV-CALHA" "" "-INSERT" "E-CALHA CFTV" "S" "1")) ;; 		ELETROCALHA | CFTV
(DEFUN C:426 () (COMMAND "-LINETYPE" "S" "BYLAYER" "" "" "-COLOR" "BYLAYER" ""  "-LAYER" "S" "_NBR-BACKBONE-CALHA" "" "-INSERT" "E-CALHA GENERICA" "S" "1")) ;; 	ELETROCALHA | BACKBONE
(DEFUN C:4211 () (COMMAND "-LINETYPE" "S" "BYLAYER" "" "" "-COLOR" "BYLAYER" ""  "-LAYER" "S" "_NBR-ELE-COM-CALHA" "" "-INSERT" "E-CALHA SEPTADA" "S" "1")) ;; 	ELETROCALHA | SEPTADO

(DEFUN C:431 () (COMMAND "-LINETYPE" "S" "BYLAYER" "" "" "-COLOR" "BYLAYER" ""  "-LAYER" "S" "_NBR-ELE-COM-CALHA" "" "-INSERT" "E-CON-PERF" "S" "1")) ;; 	CONEXÕES PERFILADO | COMUM
(DEFUN C:432 () (COMMAND "-LINETYPE" "S" "BYLAYER" "" "" "-COLOR" "BYLAYER" ""  "-LAYER" "S" "_NBR-ELE-EST-CALHA" "" "-INSERT" "E-CON-PERF" "S" "1")) ;; 	CONEXÕES PERFILADO | ESTABILIZADO
(DEFUN C:433 () (COMMAND "-LINETYPE" "S" "BYLAYER" "" "" "-COLOR" "BYLAYER" ""  "-LAYER" "S" "_NBR-CAB-CALHA" "" "-INSERT" "E-CON-PERF" "S" "1")) ;; 		CONEXÕES PERFILADO | CABEAMENTO
(DEFUN C:434 () (COMMAND "-LINETYPE" "S" "BYLAYER" "" "" "-COLOR" "BYLAYER" ""  "-LAYER" "S" "_NBR-MULT-CALHA" "" "-INSERT" "E-CON-PERF" "S" "1")) ;; 	CONEXÕES PERFILADO | MULTIMÍDIA
(DEFUN C:435 () (COMMAND "-LINETYPE" "S" "BYLAYER" "" "" "-COLOR" "BYLAYER" ""  "-LAYER" "S" "_NBR-CFTV-CALHA" "" "-INSERT" "E-CON-PERF" "S" "1")) ;; 	CONEXÕES PERFILADO | CFTV
(DEFUN C:436 () (COMMAND "-LINETYPE" "S" "BYLAYER" "" "" "-COLOR" "BYLAYER" ""  "-LAYER" "S" "_NBR-BACKBONE-CALHA" "" "-INSERT" "E-CON-PERF" "S" "1")) ;; 	CONEXÕES PERFILADO | BACKBONE
(DEFUN C:4312 () (COMMAND "-LINETYPE" "S" "BYLAYER" "" "" "-COLOR" "BYLAYER" ""  "-LAYER" "S" "_NBR-ELE-ILUEM" "" "-INSERT" "E-CON-PERF" "S" "1")) ;; 	CONEXÕES PERFILADO | ILUEM

(DEFUN C:441 () (COMMAND "-LINETYPE" "S" "BYLAYER" "" "" "-COLOR" "BYLAYER" ""  "-LAYER" "S" "_NBR-ELE-COM-CALHA" "" "-INSERT" "E-PERF" "S" "1")) ;; 		PERFILADO | COMUM
(DEFUN C:442 () (COMMAND "-LINETYPE" "S" "BYLAYER" "" "" "-COLOR" "BYLAYER" ""  "-LAYER" "S" "_NBR-ELE-EST-CALHA" "" "-INSERT" "E-PERF" "S" "1")) ;; 		PERFILADO | ESTABILIZADO
(DEFUN C:443 () (COMMAND "-LINETYPE" "S" "BYLAYER" "" "" "-COLOR" "BYLAYER" ""  "-LAYER" "S" "_NBR-CAB-CALHA" "" "-INSERT" "E-PERF" "S" "1")) ;; 			PERFILADO | CABEAMENTO
(DEFUN C:444 () (COMMAND "-LINETYPE" "S" "BYLAYER" "" "" "-COLOR" "BYLAYER" ""  "-LAYER" "S" "_NBR-MULT-CALHA" "" "-INSERT" "E-PERF" "S" "1")) ;; 		PERFILADO | MULTIMÍDIA
(DEFUN C:445 () (COMMAND "-LINETYPE" "S" "BYLAYER" "" "" "-COLOR" "BYLAYER" ""  "-LAYER" "S" "_NBR-CFTV-CALHA" "" "-INSERT" "E-PERF" "S" "1")) ;; 		PERFILADO | CFTV
(DEFUN C:446 () (COMMAND "-LINETYPE" "S" "BYLAYER" "" "" "-COLOR" "BYLAYER" ""  "-LAYER" "S" "_NBR-BACKBONE-CALHA" "" "-INSERT" "E-PERF" "S" "1")) ;; 		PERFILADO | BACKBONE
(DEFUN C:4412 () (COMMAND "-LINETYPE" "S" "BYLAYER" "" "" "-COLOR" "BYLAYER" ""  "-LAYER" "S" "_NBR-ELE-ILUEM" "" "-INSERT" "E-PERF" "S" "1")) ;; 		PERFILADO | ILUEM





;; -------------------------------------------------- DUTOS + RABICHO ------------------------------------------------------- 

(DEFUN C:511 () (COMMAND "-LINETYPE" "S" "BYLAYER" "" "" "-COLOR" "BYLAYER" ""  "-LAYER" "S" "_NBR-ELE-COM-DUTO" "" "-LINETYPE" "S" "BYLAYER" "" "" "PLINE")); 	AÇO GALVANIZADO | PLINE
(DEFUN C:512 () (COMMAND "-LINETYPE" "S" "BYLAYER" "" "" "-COLOR" "BYLAYER" ""  "-LAYER" "S" "_NBR-ELE-EST-DUTO" "" "-LINETYPE" "S" "BYLAYER" "" "" "PLINE")); 	AÇO GALVANIZADO | PLINE
(DEFUN C:513 () (COMMAND "-LINETYPE" "S" "BYLAYER" "" "" "-COLOR" "BYLAYER" ""  "-LAYER" "S" "_NBR-CAB-DUTO" "" "-LINETYPE" "S" "BYLAYER" "" "" "PLINE")); 		AÇO GALVANIZADO | PLINE
(DEFUN C:514 () (COMMAND "-LINETYPE" "S" "BYLAYER" "" "" "-COLOR" "BYLAYER" ""  "-LAYER" "S" "_NBR-MULT-DUTO" "" "-LINETYPE" "S" "BYLAYER" "" "" "PLINE"));	AÇO GALVANIZADO | PLINE
(DEFUN C:515 () (COMMAND "-LINETYPE" "S" "BYLAYER" "" "" "-COLOR" "BYLAYER" ""  "-LAYER" "S" "_NBR-CFTV-DUTO" "" "-LINETYPE" "S" "BYLAYER" "" "" "PLINE")); 	AÇO GALVANIZADO | PLINE
(DEFUN C:516 () (COMMAND "-LINETYPE" "S" "BYLAYER" "" "" "-COLOR" "BYLAYER" ""  "-LAYER" "S" "_NBR-BACKBONE-DUTO" "" "-LINETYPE" "S" "BYLAYER" "" "" "PLINE")); 	AÇO GALVANIZADO | PLINE
(DEFUN C:5112 () (COMMAND "-LINETYPE" "S" "BYLAYER" "" "" "-COLOR" "BYLAYER" ""  "-LAYER" "S" "_NBR-ELE-ILUEM" "" "-LINETYPE" "S" "BYLAYER" "" "" "PLINE")); 	AÇO GALVANIZADO | PLINE

(DEFUN C:521 () (COMMAND "-LINETYPE" "S" "BYLAYER" "" "" "-COLOR" "BYLAYER" ""  "-LAYER" "S" "_NBR-ELE-COM-DUTO" "" "-LINETYPE" "S" "BYLAYER" "" "" "SPLINE")); 	SEALTUBE | SPLINE
(DEFUN C:522 () (COMMAND "-LINETYPE" "S" "BYLAYER" "" "" "-COLOR" "BYLAYER" ""  "-LAYER" "S" "_NBR-ELE-EST-DUTO" "" "-LINETYPE" "S" "BYLAYER" "" "" "SPLINE")); 	SEALTUBE | SPLINE
(DEFUN C:523 () (COMMAND "-LINETYPE" "S" "BYLAYER" "" "" "-COLOR" "BYLAYER" ""  "-LAYER" "S" "_NBR-CAB-DUTO" "" "-LINETYPE" "S" "BYLAYER" "" "" "SPLINE")); 		SEALTUBE | SPLINE
(DEFUN C:524 () (COMMAND "-LINETYPE" "S" "BYLAYER" "" "" "-COLOR" "BYLAYER" ""  "-LAYER" "S" "_NBR-MULT-DUTO" "" "-LINETYPE" "S" "BYLAYER" "" "" "SPLINE"));	SEALTUBE | SPLINE
(DEFUN C:525 () (COMMAND "-LINETYPE" "S" "BYLAYER" "" "" "-COLOR" "BYLAYER" ""  "-LAYER" "S" "_NBR-CFTV-DUTO" "" "-LINETYPE" "S" "BYLAYER" "" "" "SPLINE")); 	SEALTUBE | SPLINE
(DEFUN C:526 () (COMMAND "-LINETYPE" "S" "BYLAYER" "" "" "-COLOR" "BYLAYER" ""  "-LAYER" "S" "_NBR-BACKBONE-DUTO" "" "-LINETYPE" "S" "BYLAYER" "" "" "SPLINE")); 	SEALTUBE | SPLINE
(DEFUN C:5211 () (COMMAND "-LINETYPE" "S" "BYLAYER" "" "" "-COLOR" "BYLAYER" ""  "-LAYER" "S" "_NBR-RAB" "" "-LINETYPE" "S" "BYLAYER" "" "" "SPLINE")); 			RABICHO | SPLINE

(DEFUN C:531 () (COMMAND "-LINETYPE" "S" "BYLAYER" "" "" "-COLOR" "BYLAYER" ""  "-LAYER" "S" "_NBR-ELE-COM-DUTO" "" "-LINETYPE" "S" "DASHDOT" "" "" "PLINE")); 	PVC PAREDE | PLINE
(DEFUN C:532 () (COMMAND "-LINETYPE" "S" "BYLAYER" "" "" "-COLOR" "BYLAYER" ""  "-LAYER" "S" "_NBR-ELE-EST-DUTO" "" "-LINETYPE" "S" "DASHDOT" "" "" "PLINE")); 	PVC PAREDE | PLINE
(DEFUN C:533 () (COMMAND "-LINETYPE" "S" "BYLAYER" "" "" "-COLOR" "BYLAYER" ""  "-LAYER" "S" "_NBR-CAB-DUTO" "" "-LINETYPE" "S" "DASHDOT" "" "" "PLINE")); 		PVC PAREDE | PLINE
(DEFUN C:534 () (COMMAND "-LINETYPE" "S" "BYLAYER" "" "" "-COLOR" "BYLAYER" ""  "-LAYER" "S" "_NBR-MULT-DUTO" "" "-LINETYPE" "S" "DASHDOT" "" "" "PLINE"));		PVC PAREDE | PLINE
(DEFUN C:535 () (COMMAND "-LINETYPE" "S" "BYLAYER" "" "" "-COLOR" "BYLAYER" ""  "-LAYER" "S" "_NBR-CFTV-DUTO" "" "-LINETYPE" "S" "DASHDOT" "" "" "PLINE")); 	PVC PAREDE | PLINE
(DEFUN C:536 () (COMMAND "-LINETYPE" "S" "BYLAYER" "" "" "-COLOR" "BYLAYER" ""  "-LAYER" "S" "_NBR-BACKBONE-DUTO" "" "-LINETYPE" "S" "DASHDOT" "" "" "PLINE")); PVC PAREDE | PLINE

(DEFUN C:541 () (COMMAND "-LINETYPE" "S" "BYLAYER" "" "" "-COLOR" "BYLAYER" ""  "-LAYER" "S" "_NBR-ELE-COM-DUTO" "" "-LINETYPE" "S" "DASHED" "" "" "PLINE")); 		PEAD NO PISO | PLINE
(DEFUN C:542 () (COMMAND "-LINETYPE" "S" "BYLAYER" "" "" "-COLOR" "BYLAYER" ""  "-LAYER" "S" "_NBR-ELE-EST-DUTO" "" "-LINETYPE" "S" "DASHED" "" "" "PLINE")); 		PEAD NO PISO | PLINE
(DEFUN C:543 () (COMMAND "-LINETYPE" "S" "BYLAYER" "" "" "-COLOR" "BYLAYER" ""  "-LAYER" "S" "_NBR-CAB-DUTO" "" "-LINETYPE" "S" "DASHED" "" "" "PLINE")); 			PEAD NO PISO | PLINE
(DEFUN C:544 () (COMMAND "-LINETYPE" "S" "BYLAYER" "" "" "-COLOR" "BYLAYER" ""  "-LAYER" "S" "_NBR-MULT-DUTO" "" "-LINETYPE" "S" "DASHED" "" "" "PLINE"));			PEAD NO PISO | PLINE
(DEFUN C:545 () (COMMAND "-LINETYPE" "S" "BYLAYER" "" "" "-COLOR" "BYLAYER" ""  "-LAYER" "S" "_NBR-CFTV-DUTO" "" "-LINETYPE" "S" "DASHED" "" "" "PLINE")); 			PEAD NO PISO | PLINE
(DEFUN C:546 () (COMMAND "-LINETYPE" "S" "BYLAYER" "" "" "-COLOR" "BYLAYER" ""  "-LAYER" "S" "_NBR-BACKBONE-DUTO" "" "-LINETYPE" "S" "DASHED" "" "" "PLINE")); 		PEAD NO PISO | PLINE


;; -------------------------------------------------- TEXTOS E ROTA DE CABOS------------------------------------------------------- 


(DEFUN C:551 () (COMMAND "-LINETYPE" "S" "BYLAYER" "" "" "-COLOR" "BYLAYER" "-LAYER" "S" "_NBR-TXT" "" "MLEADER")); MLEADER
(DEFUN C:552 () (COMMAND "-LINETYPE" "S" "BYLAYER" "" "" "-COLOR" "BYLAYER" "-LAYER" "S" "_NBR-TXT" "" "MTEXT"));  MTEXT
(DEFUN C:553 () (COMMAND "-LINETYPE" "S" "BYLAYER" "" "" "-COLOR" "BYLAYER" "-LAYER" "S" "_NBR-TXT" "" "DTEXT"));  DTEXT
(DEFUN C:554 () (COMMAND "-LINETYPE" "S" "BYLAYER" "" "" "-COLOR" "BYLAYER" ""  "-LAYER" "S" "_NBR-ELE-ROTA CABOS" "" "-INSERT" "E-ROTA DE CABOS" "S" "1")) ;; 	ROTA DE CABOS
